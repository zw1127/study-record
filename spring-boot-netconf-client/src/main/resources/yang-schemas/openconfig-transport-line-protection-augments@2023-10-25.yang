module openconfig-transport-line-protection-augments {

  yang-version "1";

  // namespace
  namespace "http://openconfig.net/yang/optical-transport-line-protection-augment";

  prefix "oc-line-protect-aug";

  import openconfig-extensions { prefix oc-ext; }
  import openconfig-platform { prefix oc-platform; }
  import openconfig-transport-line-protection { prefix oc-line-protect; }

  // meta
  organization "OpenConfig working group";

  contact
    "OpenConfig working group
    www.openconfig.net";

  description
    "Augments optical-transport-line-protection.";
  
  oc-ext:openconfig-version "0.1.0";
  
  revision "2023-10-25" {
    description
      "Initial release.";
    reference "0.1.0";
  }

  // grouping statements
  grouping ochp-top {
    description
      "Top-level grouping for configuration and operational state
      data for electrical supervisory channels for APS.";

    container protected-optical-channels {
      description
        "Enclosing container.";
      
      list optical-channel {
        key "name";
        description "List of optical channels protected by APS.";

        leaf name {
          type leafref {
            path "../config/name";
          }
          description
            "Index of the electrical-supervisory-channel.";
        }

        container config {
          uses ochp-config;
        }

        container state {
          config false;
          uses ochp-config;
          uses ochp-state;
        }
      }
    }
  }

  grouping ochp-config {
    leaf name {
      type leafref {
        path "/oc-platform:components/oc-platform:component/" +
        "oc-platform:name";
      }
      description
        "Reference to system-supplied name of the optical-channel
        which under the protection of APS.";
    }
  }

  grouping ochp-state {
  }

  // data definition statements

  // augment statements
  augment "/oc-line-protect:aps/oc-line-protect:aps-modules/oc-line-protect:aps-module" {
    uses ochp-top;
  }

}
