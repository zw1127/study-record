module fiberhome-transport-augment {

  yang-version "1";

  // namespace
  namespace "http://www.fiberhome.com/yang/openconfig-transport-augment";

  prefix "fh-opt-aug";

  // import some basic types
  import openconfig-terminal-device { prefix oc-opt-term; }
  import openconfig-yang-types {prefix oc-yang; }
  import openconfig-platform { prefix oc-platform; }
  import openconfig-platform-transceiver { prefix oc-transceiver; }
  import openconfig-types { prefix oc-types; }
  import openconfig-transport-types { prefix oc-opt-types; }
  import ietf-inet-types {prefix ietf-inet; }

  // meta
  organization "Fiberhome working group";

  contact
    "Fiberhome working group
    www.fiberhome.com";

  description
    "This model describes fiberhome transport augmentation.
    It is an informal version, which is only
    available for fiberhome internal discussion.";

  revision "2021-08-30" {
    description
      "add tributary-slot-bits for logical channel slot assigned.";
    reference "0.1.0";
  }

  identity PT_800G {
    base oc-opt-types:TRANSCEIVER_PORT_TYPE;
    description "Ethernet 800G";
  }

  identity PT_OTUC6 {
    base oc-opt-types:TRANSCEIVER_PORT_TYPE;
    description "OTUC6";
  }

  identity PT_OTUC8 {
    base oc-opt-types:TRANSCEIVER_PORT_TYPE;
    description "OTUC8";
  }

  identity PROT_STM1 {
    base oc-opt-types:TRIBUTARY_PROTOCOL_TYPE;
    description "STM 1 protocol";
  }

  identity PROT_STM4 {
    base oc-opt-types:TRIBUTARY_PROTOCOL_TYPE;
    description "STM 4 protocol";
  }

  identity PROT_1FE {
    base oc-opt-types:TRIBUTARY_PROTOCOL_TYPE;
    description "1F Ethernet protocol";
  }

  identity PROT_1GFC {
    base oc-opt-types:TRIBUTARY_PROTOCOL_TYPE;
    description "1 GFC Ethernet protocol";
  }

  identity PROT_2GFC {
    base oc-opt-types:TRIBUTARY_PROTOCOL_TYPE;
    description "2 GFC Ethernet protocol";
  }

  identity PROT_4GFC {
    base oc-opt-types:TRIBUTARY_PROTOCOL_TYPE;
    description "4 GFC Ethernet protocol";
  }

  identity PROT_8GFC {
    base oc-opt-types:TRIBUTARY_PROTOCOL_TYPE;
    description "8 GFC Ethernet protocol";
  }

  identity PROT_10GFC {
    base oc-opt-types:TRIBUTARY_PROTOCOL_TYPE;
    description "10 GFC Ethernet protocol";
  }

  identity PROT_16GFC {
    base oc-opt-types:TRIBUTARY_PROTOCOL_TYPE;
    description "16 GFC Ethernet protocol";
  }

  identity PROT_32GFC {
    base oc-opt-types:TRIBUTARY_PROTOCOL_TYPE;
    description "32 GFC Ethernet protocol";
  }

  identity PROT_ODU0 {
    base oc-opt-types:TRIBUTARY_PROTOCOL_TYPE;
    description "ODU 0 protocol";
  }

  identity PROT_ODU1 {
    base oc-opt-types:TRIBUTARY_PROTOCOL_TYPE;
    description "ODU 1 protocol";
  }

  identity PROT_OTU1 {
    base oc-opt-types:TRIBUTARY_PROTOCOL_TYPE;
    description "OTU 1 protocol";
  }

  typedef tributary-slot-bits {
    type string;
    description "type for tributary slot bits.";
  }

  typedef fec-mode-type {
    type enumeration {
      enum close {
        description "Do not use FEC.";
      }
      enum normal {
        description "Normal FEC.";
      }
      enum super {
        description "Super FEC.";
      }
      enum super-i4 {
        description "Super i4 FEC.";
      }
      enum super-i7 {
        description "Super i7 FEC.";
      }
    }
    description "Fec mode for otu.";
  }

  grouping tributary-slot-grouping {
    description
      "Adding tributary slot bits to logical channel.";

    leaf tributary-slot-bits {
      type tributary-slot-bits;
      description
        "assignment slots.";
    }
  }

  grouping fec-mode-grouping {
    description
      "Adding fec mode for otu.";

    leaf fec-mode {
      type fec-mode-type;
      description
        "Otu fec mode.";
    }
  }

  grouping encrypted-channel-grouping {
    description
      "Adding encrypted channel config for logical channel.";

    container encrypted-channel {
      description
        "encrypted channel info.";

      leaf enable {
        type boolean;
        default false;
        description
          "Whether need encrypt.";
      }

      leaf dest-address {
        type ietf-inet:ip-address;
        description
          "Destination ip address.";
      }

      container dest-port {
        description
          "destination port information.";

        leaf dest-transceiver {
          type leafref {
            path "/oc-platform:components/oc-platform:component/" +
            "oc-platform:name";
          }
          description
            "Reference to the transceiver carrying the input signal
            for the logical channel.  If specific physical channels
            are mapped to the logical channel (as opposed to all
            physical channels carried by the transceiver), they can be
            specified in the list of physical channel references.";
        }

        leaf dest-physical-channel {
          type leafref {
            path "/oc-platform:components/oc-platform:component/" +
            "oc-transceiver:transceiver/" +
            "oc-transceiver:physical-channels/" +
            "oc-transceiver:channel/oc-transceiver:index";
          }
          description
            "This node should be populated with references
            to the client physical channels that feed this logical
            channel from the transceiver specified in the 'transceiver'
            leaf, which must be specified.  If this leaf-list is empty,
            all physical channels in the transceiver are assumed to be
            mapped to the logical channel.";
        }
      }

      leaf auth-info {
        type string {
          length "1..32";
        }
        default "FIBERHOME OTN ENCRYPTION";
        description
          "auth info";
      }

      leaf key-interval {
        type enumeration {
          enum 10m {
            description "10 minutes.";
          }
          enum 30m {
            description "30 minutes.";
          }
          enum 1h {
            description "1 hour.";
          }
          enum 3h {
            description "3 hours.";
          }
          enum 6h {
            description "6 hours.";
          }
          enum 1d {
            description "1 day.";
          }
          enum 7d {
            description "7 days.";
          }
          enum 30d {
            description "30 days.";
          }
        }
        default 30m;
        description
          "key interval.";
      }

      leaf dh-datalength {
        type enumeration {
          enum 1024bits {
            description "1024 bits";
          }
          enum 2048bits {
            description "2048 bits";
          }
        }
        default 2048bits;
        description
          "key bits length.";
      }

      leaf key-source {
        type enumeration {
          enum dh {
            description "DH algorithm.";
          }
          enum qkd {
            description "Quantum distribution.";
          }
        }
        default dh;
        description
          "key source.";
      }
    }
  }

  augment "/oc-opt-term:terminal-device/oc-opt-term:logical-channels/" +
  "oc-opt-term:channel/oc-opt-term:logical-channel-assignments/" +
  "oc-opt-term:assignment/oc-opt-term:config" {

    description
      "Adding tributary slot bits to logical channel.";

    uses tributary-slot-grouping;
  }

  augment "/oc-opt-term:terminal-device/oc-opt-term:logical-channels/" +
  "oc-opt-term:channel/oc-opt-term:logical-channel-assignments/" +
  "oc-opt-term:assignment/oc-opt-term:state" {

    description
      "Adding tributary slot bits to logical channel.";

    uses tributary-slot-grouping;
  }

  augment "/oc-platform:components/oc-platform:component/" +
  "oc-opt-term:optical-channel/oc-opt-term:state" {
    description
      "add min-output-power and max-output-power to optical channel.";

    leaf min-output-power {
      type decimal64 {
        fraction-digits 2;
      }
      units dBm;
      description
        "Min output optical power level of the optical channel,
        expressed in increments of 0.01 dBm (decibel-milliwats)";
    }

    leaf max-output-power {
      type decimal64 {
        fraction-digits 2;
      }
      units dBm;
      description
        "Max output optical power level of the optical channel,
        expressed in increments of 0.01 dBm (decibel-milliwats)";
    }

    leaf actual-modulation {
      type string;
      description
        "Actual modulation for optical module.";
    }
  }

  augment "/oc-opt-term:terminal-device/oc-opt-term:logical-channels/" +
  "oc-opt-term:channel/oc-opt-term:otn/oc-opt-term:config" {

    description
      "Adding fec mode for otu.";

    uses fec-mode-grouping;
    uses encrypted-channel-grouping;
  }

  augment "/oc-opt-term:terminal-device/oc-opt-term:logical-channels/" +
  "oc-opt-term:channel/oc-opt-term:otn/oc-opt-term:state" {

    description
      "Adding fec mode for otu.";

    uses fec-mode-grouping;
    uses encrypted-channel-grouping;
  }

  augment "/oc-opt-term:terminal-device/oc-opt-term:logical-channels/" +
  "oc-opt-term:channel/oc-opt-term:ethernet/oc-opt-term:config" {

    description
      "Adding fec mode for otu.";

    uses encrypted-channel-grouping;
  }

  augment "/oc-opt-term:terminal-device/oc-opt-term:logical-channels/" +
  "oc-opt-term:channel/oc-opt-term:ethernet/oc-opt-term:state" {

    description
      "Adding fec mode for otu.";

    uses encrypted-channel-grouping;
  }
}
