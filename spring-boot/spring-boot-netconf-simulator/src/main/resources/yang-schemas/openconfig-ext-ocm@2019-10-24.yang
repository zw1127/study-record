module openconfig-ext-ocm {

  yang-version "1";

  // namespace
  namespace "http://openconfig.net/yang/openconfig-ext-ocm";

  prefix "oc-ext-ocm";

  // import some basic types
  import openconfig-platform { prefix oc-platform; }
  import openconfig-ext-types { prefix oc-ext-types; }
  import openconfig-transport-types { prefix oc-opt-types; }

  // meta
  organization "OpenConfig working group";

  contact
    "OpenConfig working group
      www.openconfig.net";

  description
    "This model describes operational state data for an optical
    channel monitor (OCM) for optical transport line system
    elements such as wavelength routers (ROADMs) and amplifiers.";

  revision "2019-10-24" {
    description
      "Migrate from using power spectral densisty to using power
      target values";
    reference "0.4.0";
  }    

    rpc get-ocm-data {
        description "get-ocm operation.";
        input    {
            leaf name {
                type leafref {
                    path "/oc-platform:components/oc-platform:component/oc-platform:name";
                }
                description 
					        "Reference to system-supplied name of the port on the
					        optical channel monitor (OCM). If this port is embedded
					        in another card (i.e. an amplifier card) the device
					        should still define a port representing the OCM even if
					        it is internal and not physically present on the
					        faceplate of the card";
					            }
            
            leaf monitor-port {
                type leafref {
                    path "/oc-platform:components/oc-platform:component/oc-platform:name";
                }
                description 
                    "Reference to system-supplied name of the port that the
						        channel monitor is physically connected to. This port
						        will be of type MONITOR. This port is a tap off of the
						        monitored-port and would be in the same card as the
						        monitored port. If this port is embedded in another card
						        (i.e. an amplifier card) the device should still define
						        a port representing the monitor port if it is internal
						        and not physically present on the faceplate of the card";
            }
        }
        output    {
            leaf get-ocm-result {
                type oc-ext-types:operation-result;
                description "get ocm opearation result.";
            }
            
			      leaf file-name {
			        type string;
			        mandatory true;
			        description
			           "the ocm file name";
			      } 
            
            
        }
    }  
  
  rpc start-auto-ocm {
        description "start-ocm operation.";
        input    {
            leaf name {
                type leafref {
                    path "/oc-platform:components/oc-platform:component/oc-platform:name";
                }
                description 
					        "Reference to system-supplied name of the port on the
					        optical channel monitor (OCM). If this port is embedded
					        in another card (i.e. an amplifier card) the device
					        should still define a port representing the OCM even if
					        it is internal and not physically present on the
					        faceplate of the card";
					            }
            
            leaf monitor-port {
                type leafref {
                    path "/oc-platform:components/oc-platform:component/oc-platform:name";
                }
                description 
                    "Reference to system-supplied name of the port that the
						        channel monitor is physically connected to. This port
						        will be of type MONITOR. This port is a tap off of the
						        monitored-port and would be in the same card as the
						        monitored port. If this port is embedded in another card
						        (i.e. an amplifier card) the device should still define
						        a port representing the monitor port if it is internal
						        and not physically present on the faceplate of the card";
            }
            
           leaf auto-scan-interval {
				type uint32;
				units "minute";
                description 
                    "auto scan interval";
            }
            
            leaf start-frequency {
				type oc-opt-types:frequency-type;
			    description
              "The start frequency for the spectrum defined by this channel monitor";
            }
			     
            leaf channel-num  {
				        type uint32;
                description 
                    "channel-num";
            } 

			     leaf sweep-interval {
			      type enumeration {
			        enum 50GHz {
			          description
			            "sweep-interval is 50GHz";
			        }
			        enum 75GHz {
			          description
			            "sweep-interval is 75GHz";
			        }
			        enum 100GHz {
			          description
			            "sweep-interval is 100GHz";
			        }
			        enum 125GHz {
			          description
			            "sweep-interval is 125GHz";
			        }
			        enum 150GHz {
			          description
			            "sweep-interval is 150GHz";
			        }
			        enum FLEXGRID {
			          description
			            "sweep-interval is flexgrid";
			        }
			      }
				default 75GHz;
			      description
			        "OCM'S configuration item";            
			    }     
            
        }
        output    {
            leaf start-auto-ocm-result {
                type oc-ext-types:operation-result;
                description "start auto scan ocm opearation result.";
            }            
        }
    
  
}

        rpc stop-auto-ocm {
        description "start-auto-ocm operation.";
        input    {
            leaf name {
                type leafref {
                    path "/oc-platform:components/oc-platform:component/oc-platform:name";
                }
                description 
					        "Reference to system-supplied name of the port on the
					        optical channel monitor (OCM). If this port is embedded
					        in another card (i.e. an amplifier card) the device
					        should still define a port representing the OCM even if
					        it is internal and not physically present on the
					        faceplate of the card";
					            }
            
            leaf monitor-port {
                type leafref {
                    path "/oc-platform:components/oc-platform:component/oc-platform:name";
                }
                description 
                    "Reference to system-supplied name of the port that the
						        channel monitor is physically connected to. This port
						        will be of type MONITOR. This port is a tap off of the
						        monitored-port and would be in the same card as the
						        monitored port. If this port is embedded in another card
						        (i.e. an amplifier card) the device should still define
						        a port representing the monitor port if it is internal
						        and not physically present on the faceplate of the card";
            }          
        }
        output    {
            leaf stop-auto-ocm-result {
                type oc-ext-types:operation-result;
                description "stop auto scan ocm opearation result.";
            }            
        }
    
  }
}
