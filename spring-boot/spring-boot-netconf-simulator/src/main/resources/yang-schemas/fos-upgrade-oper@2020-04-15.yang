module fos-upgrade-oper {

  namespace "http://fiberhome.com/fhnw/upgrademanager/fos-upgrade-oper";

  prefix "upgrade-oper";
  
  import fos-datatype-common {
      prefix "co-type";
    }
	
  
  organization "Fiberhome Systems, Inc.";

  contact
    "Fiberhome Systems, Inc.
     Postcode: 430073
     Address: No.6,Gaoxin 4 Rd,Donghu Hi-Tech Development Zone, Wuhan, Hubei
     Tel: +XXXXXXXXXXXX
     E-mail: yang-author@fiberhome.com";

  description
    "This module contains a collection of YANG definitions
     for Fiberhome upgrade info.
     
     This module contains definitions
     for the following management objects:
         ***
     E-mail: yang-author@fiberhome.com
     All rights reserved.";

  revision 2020-04-15 {
    description "Add auto rollback for upgrade.";
  }

  revision 2019-10-10 {
    description "Add COMMIT_BACKUP_MAINBOARD for commit-type.";
  }

  revision 2018-12-12 {
    description "Initial version.";
  }
    
  typedef upgrade-global-state {
    type enumeration {
      enum IDLE {
        value 0;
      }
      enum BUSY {
        value 1;
      }
      enum CANSTARTUP {
        value 2;
      }
      enum CANCOMMIT {
        value 3;
      }
    }
    description "upgrade task global state.";
  }

  typedef startup-state {
    type co-type:string64 {
      pattern '(startup-processing-(([0-9]%)|([1-9][0-9]%)|(100%)))|(startup-successful|file-not-exist|file-error|startup-error|backup-file-error)' {
        description 
          "(startup-processing-x%|startup-successful|file-not-exist|file-error|startup-error|backup-file-error)
           x:0~100";
      }
    }
  }

  typedef auto-rollback-switch {
    type enumeration {
      enum OFF {
        value 0;
      }
      enum ON {
        value 1;
      }
    }
    description "disable or enable state.";
  }

  container upgrade-oper {
    config false;
    description
      "upgrade process information.";
    container upgrade-global-status {

      description
        "upgrade global status.";    
    
      leaf filename {
        type string {
          length "1..64";
        }
        mandatory true;

        description
          "upgrade remote path and name.";
      }
        
      leaf upgrade-global-state {
        type upgrade-global-state;
        description
          "upgrade global state.";
      }
    }

    container startup-status {
      description "startup status informaiton";

      leaf startup-state {
        type startup-state;
        description
          "detailed startup state info.";
      }

    }

    container auto-rollback-state {
      description "auto-rollback state informaiton";

      leaf switch-flag {
        type auto-rollback-switch;
        description
          "auto rollback state, disable or enable.";
      }

      leaf timeout {
        type uint32;
        units "minute";
        description
          "Indicate a timeout in minutes that trigger auto rollback.";
      }
    }
  }

  /* remote startup CMD RPC */
  rpc startup-cmd {
    description "startup operation.";
    input {

      leaf filename {
        type string {
          length "1..64";
        }
        mandatory true;
      }
    }
  }

  rpc startup-commit-cmd {

    description "startup commit command";
    input {

      leaf delay {
        type uint32;
      }
      leaf commit-type {
        type enumeration {
          enum COMMIT_SLOT {
            value 1;
          }

          enum COMMIT_ALL {
            value 2;
          }

          enum COMMIT_BACKUP_MAINBOARD {
            value 3;
          }
              
        }
        mandatory true;
                  
      }

    }
  }

  /* startup rollback RPC */
  rpc startup-rollback-cmd;

  /* startup reset RPC */
  rpc startup-reset-cmd;

  rpc set-auto-rollback {
    description "set auto rollback command";
    input {

      leaf switch-flag {
        type auto-rollback-switch;
        description
          "set auto rollback disable or enable.";
        mandatory true;
      }

      leaf timeout {
        type uint32 {
          range "10..360";
        }
        units "minute";
        description
          "Indicate a timeout in minutes that trigger auto rollback.";
      }
    }
  }
  
  /* startup notification */
  notification startup-over
  {
	leaf filename {
        type string {
          length "1..64";
        }
      }
	  
	leaf startup-state {
        type startup-state;
        description
          "detailed startup state info.";
      }
  }
}
