module openconfig-ext-action {

  yang-version "1";

  // namespace
  namespace "http://openconfig.net/yang/openconfig-ext-action";

  prefix "oc-ext-action";

  // import some basic types


  // meta
  organization "OpenConfig working group";

  contact
    "OpenConfig working group
      www.openconfig.net";

  description
    "This model describes operational state data for an optical
    channel monitor (OCM) for optical transport line system
    elements such as wavelength routers (ROADMs) and amplifiers.";

  revision "2019-10-24" {
    description
      "Migrate from using power spectral densisty to using power
      target values";
    reference "0.4.0";
  }   
  
  typedef action-type {
    type enumeration  {
      enum ftp-upload-file  {
        description
        "the file is database";
      }
      enum ftp-download-file {
        description
        "the file is image";
      }    
      enum get-ocm {
        description
        "the file is image and database";
      }    
      enum get-otdr {
        description
        "the file is certificate";
      }     
      enum get-constellation {
        description
        "the file is license";
      }   
    }    
  } 
  
  typedef action-result {
    type enumeration {
      enum SUCCESS {
        description
        "The RPC action is success";
      }
      enum FAIL {
        description
        "The RPC action is fail";
      }     
    }    
  }  
  
  
grouping action-state {
    description
      "Operational state data for device action";
      
    leaf file-name {
      type string;
      description
        "action file name";
    }      
          
    leaf action {
      type action-type;
      description
        "action type";
    }

    leaf result {
      type action-result;
      description
        "result";
    }
 }  

  grouping action-config {
    description
      "Configuration data for device alarms";

    leaf file-name {
      type string;
      description
        "action file name";
    }  
  }

  grouping action-top {
    description
      "Top-level grouping for device action";

    container actions {
      description
        "Top-level container for device action";

      list action {
        key "file-name";
        description
          "List of actions, keyed by a unique file-name";

        leaf file-name {
          type leafref {
            path "../state/file-name";
          }

          description
            "References the unique action ";
        }
        
        container config {
          description
            "Configuration data for each action";

          uses action-config;
        }

        container state {
          config false;

          description
            "Operational state data for a action";
            
          uses action-state;
        }
      }
    }
  }
  
  
  uses action-top;
  
  notification action-notification {

    container update {
      uses action-top;
    }

  }  
  
}
