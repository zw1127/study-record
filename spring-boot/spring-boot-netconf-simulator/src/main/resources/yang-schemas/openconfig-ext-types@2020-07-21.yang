module openconfig-ext-types {

  namespace "http://openconfig.net/yang/openconfig-ext-types";

  prefix "oc-ext-types";

  organization "Fiberhome Systems, Inc.";

  contact
    "Fiberhome Systems, Inc.
    Postcode: 430073
    Address: No.6,Gaoxin 4 Rd,Donghu Hi-Tech Development Zone, Wuhan, Hubei
    Tel: +XXXXXXXXXXXX
    
    E-mail: yang- author@fiberhome.com";

  description
    "This module contains a collection of YANG definitions
    for Fiberhome FOS-VBRAS xxx package configuration.
    
    This module contains definitions
    for the following management objects:
    	***
    E-mail: yang- author@fiberhome.com
    All rights reserved.";

  revision "2020-07-21" {
    description
      "Openconfig extent type defines.";
  }

  typedef operation-result {
    type enumeration {
      enum success {
        value 0;
        description "Operation succeed.";
      }
      enum fail {
        value 1;
        description "Operation failed.";
      }
    }
    description
      "Operation result,success or failed.";
  }

}
