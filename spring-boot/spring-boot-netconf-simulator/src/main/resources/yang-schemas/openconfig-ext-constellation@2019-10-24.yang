module openconfig-ext-constellation {

  yang-version "1";

  // namespace
  namespace "http://openconfig.net/yang/openconfig-ext-constellation";

  prefix "oc-ext-constellation";

  // import some basic types
  import openconfig-platform { prefix oc-platform; }
  import openconfig-ext-types { prefix oc-ext-types; }

  // meta
  organization "OpenConfig working group";

  contact
    "OpenConfig working group
      www.openconfig.net";

  description
    "This model describes operational state data for
    constellation for optical transport line system
    elements such as wavelength routers (ROADMs) and amplifiers.";

  revision "2019-10-24" {
    description
      "Migrate from using power spectral densisty to using power
      target values";
    reference "0.4.0";
  }    

    rpc get-constellation-data {
        description "get-constellation operation.";
        input    {
            leaf line-port {
                type leafref {
                    path "/oc-platform:components/oc-platform:component/oc-platform:name";
                }
                description 
                    "Reference to system-supplied name of the port that the
						        channel monitor is physically connected to. This port
						        will be of type MONITOR. This port is a tap off of the
						        monitored-port and would be in the same card as the
						        monitored port. If this port is embedded in another card
						        (i.e. an amplifier card) the device should still define
						        a port representing the monitor port if it is internal
						        and not physically present on the faceplate of the card";
            }
        }
        output    {
            leaf get-constellation-result {
                type oc-ext-types:operation-result;
                description "get constellation opearation result.";
            }
            
			      leaf file-name {
			        type string;
			        mandatory true;
			        description
			           "the ocm file name";
			      }
        }
    }  
  
}
