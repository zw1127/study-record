module openconfig-ext-physical-links {

  yang-version "1";
  
  // namespace
  namespace "http://openconfig.net/yang/openconfig-ext-physical-links";
  
  prefix oc-phy-links;
  
  import ietf-inet-types {
    prefix inet;
  }

  // meta
  organization "OpenConfig working group";
  
  contact
    "OpenConfig working group
    www.openconfig.net";
	
  description
    "This module definitions for physical links.";

  revision 2020-07-01 {
    description
      "Version 0.0.1";
  }
  
  typedef link-state {
    type enumeration {
      enum "down" {
        value 0;
      }
      enum "up" {
        value 1;
      }
    }
    description
      "link state.";
  }
  
  grouping user-description-grp {
    description
      "user description group";
    leaf user-description {
      type string;
      description
        "user provided description";
    }
  }
  
  grouping port-ip-address {
    leaf port-ip-address {
      type inet:ip-address;
      description
        "Ip address of port.";
    }
  }
  
  grouping port-name {
    uses port-ip-address;
    leaf port-name {
      type string;
      description
        "Port identifier. Unique within the context of a circuit-pack.";
    }
  }

  grouping physical-link {
    leaf physical-link-name {
      type string;
    }
    leaf is-physical {
      type boolean;
      description
        "is the entity physical or logical";
    }
    uses user-description-grp;
    container source {
      uses port-name {
        refine "port-ip-address" {
          mandatory true;
        }
        refine "port-name" {
          mandatory true;
        }
      }
    }
    container destination {
      uses port-name {
        refine "port-ip-address" {
          mandatory true;
        }
        refine "port-name" {
          mandatory true;
        }
      }
    }
    leaf link-state {
      type link-state;
      description
        "Link State of the physical link. Whether it is up or down.";
    }
  }
  
  grouping physical-links {
    description
      "YANG definitions for physical links.
       - physical links (fiber, cables,etc.) between ports within a node. ";
    list physical-link {
      key "physical-link-name";
      uses physical-link;
    }
  }
  
  container physical-links {
	description
      "YANG definitions for physical links.
       - physical links (fiber, cables,etc.) between ports within a node. ";
	   
    uses physical-links;
  }
}
